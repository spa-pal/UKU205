IBEP-3U DEFINITIONS ::= BEGIN

IMPORTS
	enterprises
		FROM RFC1155-SMI
	OBJECT-TYPE
		FROM RFC-1212
	TRAP-TYPE
		FROM RFC-1215
	DisplayString
		FROM RFC-1213;


-- Системы ПромАвтоматики

entSPA-SIB           OBJECT IDENTIFIER ::= { enterprises 33183 }
ibep1U               OBJECT IDENTIFIER ::= { entSPA-SIB 10 }
displayDeviceInfo    OBJECT IDENTIFIER ::= { ibep1U 1 }
dipslayMains         OBJECT IDENTIFIER ::= { ibep1U 2 }
displayLoad          OBJECT IDENTIFIER ::= { ibep1U 3 }
displayBatteries  OBJECT IDENTIFIER ::= { ibep1U 5 }
displayBatteriesMass  OBJECT IDENTIFIER ::= { displayBatteries 1 }
displayBatteriesCell  OBJECT IDENTIFIER ::= { displayBatteries 2 }
displaySpecials      OBJECT IDENTIFIER ::= { ibep1U 6 }
displayDEBUG         OBJECT IDENTIFIER ::= { ibep1U 13 }
displayExtTemper     OBJECT IDENTIFIER ::= { ibep1U 16 }



displayDeviceInfoSerial  OBJECT-TYPE
	SYNTAX     INTEGER (0..65535)
	ACCESS     read-only
	STATUS     mandatory
	DESCRIPTION 
		""
	::= { displayDeviceInfo 2 }


displayDeviceLocation  OBJECT-TYPE
	SYNTAX     DisplayString (SIZE(69))
	ACCESS     read-write
	STATUS     mandatory
	DESCRIPTION 
		"User-defined information about the location of the device. Maximum 64 Latin characters"
	::= { displayDeviceInfo 5 }

displayDeviceInfoNumOfBat  OBJECT-TYPE
	SYNTAX     INTEGER
	ACCESS     read-only
	STATUS     mandatory
	DESCRIPTION 
		"Number of batteries in the system"
	::= { displayDeviceInfo 6 }

displayDeviceInfoNumOfBps  OBJECT-TYPE
	SYNTAX     INTEGER
	ACCESS     read-only
	STATUS     mandatory
	DESCRIPTION 
		"Number of rectifiers (PSU) in the system"
	::= { displayDeviceInfo 7 }

displayDeviceInfoNumOfEvents  OBJECT-TYPE
	SYNTAX     INTEGER
	ACCESS     read-only
	STATUS     mandatory
	DESCRIPTION 
		"Depth of event list (max 64)"
	::= { displayDeviceInfo 8 }

displayDeviceModel  OBJECT-TYPE
	SYNTAX     DisplayString (SIZE(30))
	ACCESS     read-only
	STATUS     mandatory
	DESCRIPTION 
		"Product model (only Latin characters)"
	::= { displayDeviceInfo 9 }

dipslayMainsVoltage  OBJECT-TYPE
	SYNTAX     INTEGER (0..65535)
	ACCESS     read-only
	STATUS     mandatory
	DESCRIPTION 
		"Primary power supply voltage, resolution 1V"
	::= { dipslayMains 1 }

dipslayMainsFrequency  OBJECT-TYPE
	SYNTAX     INTEGER (0..65535)
	ACCESS     read-only
	STATUS     mandatory
	DESCRIPTION 
		"Primary power supply frequency, resolution 0.1Hz, example "499" means 49.9Hz"
	::= { dipslayMains 2 }

dipslayMainsStatus  OBJECT-TYPE
	SYNTAX     INTEGER { norm(0),alarm(1)}
	ACCESS     read-only
	STATUS     mandatory
	DESCRIPTION 
		"Primary power supply state"
	::= { dipslayMains 3 }

-- //


displayLoadVoltage  OBJECT-TYPE
	SYNTAX     INTEGER (0..65535)
	ACCESS     read-only
	STATUS     mandatory
	DESCRIPTION 
		"Load voltage, resolution 0.1V (example "123" means 12.3V)"
	::= { displayLoad 1 }

displayLoadCurrent  OBJECT-TYPE
	SYNTAX     INTEGER (0..65535)
	ACCESS     read-only
	STATUS     mandatory
	DESCRIPTION 
		"Load current, resolution 0.1A (example "123" means 12.3A)"
	::= { displayLoad 2 }

displayPSUTable  OBJECT-TYPE
	SYNTAX SEQUENCE OF DisplayPSUEntry
	ACCESS     not-accessible
	STATUS     mandatory
	DESCRIPTION 
		"Rectifier status table"
	::= { ibep1U 4 }

displayPSUEntry  OBJECT-TYPE
	SYNTAX 	DisplayPSUEntry
	ACCESS     not-accessible
	STATUS     mandatory
	DESCRIPTION 
		"PSU listing"
	INDEX { displayPSUnumber }
	::= { displayPSUTable 1 }

DisplayPSUEntry ::= SEQUENCE {
	displayPSUnumber
		INTEGER,
	displayPSUVoltage
		INTEGER,
	displayPSUCurrent
		INTEGER,
	displayPSUTemperature
		INTEGER,
	displayPSUStatus
		INTEGER
}

displayPSUnumber  OBJECT-TYPE
	SYNTAX     INTEGER
	ACCESS     read-only
	STATUS     mandatory
	DESCRIPTION 
		"Rectifier serial number"
	::= { displayPSUEntry 1 }

displayPSUVoltage  OBJECT-TYPE
	SYNTAX     INTEGER (0..65535)
	ACCESS     read-only
	STATUS     mandatory
	DESCRIPTION 
		"Rectifier output voltage, resolution 0.1V (example "123" means 12.3V)"
	::= { displayPSUEntry 2 }

displayPSUCurrent  OBJECT-TYPE
	SYNTAX     INTEGER (0..65535)
	ACCESS     read-only
	STATUS     mandatory
	DESCRIPTION 
		"Rectifier output current, resolution 0.1A (example "123" means 12.3A)"
	::= { displayPSUEntry 3 }

displayPSUTemperature  OBJECT-TYPE
	SYNTAX     INTEGER (0..65535)
	ACCESS     read-only
	STATUS     mandatory
	DESCRIPTION 
		"Internal temperature of the rectifier, 1 degree Celsius resolution (example "30" means 30 degrees Celsius)"
	::= { displayPSUEntry 4 }

displayPSUStatus  OBJECT-TYPE
	SYNTAX     INTEGER { Rectifier is work(1), rectifier locked into standby(32), failure rectifier overheating(2), failure output voltage too low(4), failure output voltage too high(8)}
	ACCESS     read-only
	STATUS     mandatory
	DESCRIPTION 
		"PSU status flags"
	::= { displayPSUEntry 5 }

displayBatteriesMassVoltage  OBJECT-TYPE
	SYNTAX     INTEGER (0..65535)
	ACCESS     read-only
	STATUS     mandatory
	DESCRIPTION 
		"Battery voltage, resolution 0.1V (example "123" means 12.3V)"
	::= { displayBatteriesMass 2 }
	
	

displayBatteriesMassCurrent  OBJECT-TYPE
	SYNTAX     INTEGER (0..65535)
	ACCESS     read-only
	STATUS     mandatory
	DESCRIPTION 
		"Battery current, resolution 0.01A (example "123" means 1.23A charge, "-123" means 1.23A discharge)"
	::= { displayBatteriesMass 3 }

displayBatteriesMassTemperature  OBJECT-TYPE
	SYNTAX     INTEGER (0..65535)
	ACCESS     read-only
	STATUS     mandatory
	DESCRIPTION 
		"Internal temperature of the battery, 1 degree Celsius resolution (example "30" means 30 degrees Celsius)"
	::= { displayBatteriesMass 4 }

displayBatteriesMassCapacity  OBJECT-TYPE
	SYNTAX     INTEGER (0..65535)
	ACCESS     read-only
	STATUS     mandatory
	DESCRIPTION 
		"Battery capacity, resolution 0.1 a * h (example "123" means 12.3 a * h )"
	::= { displayBatteriesMass 5 }

displayBatteriesMassCharge  OBJECT-TYPE
	SYNTAX     INTEGER (0..65535)
	ACCESS     read-only
	STATUS     mandatory
	DESCRIPTION 
		"Battery charge, resolution 1%"
	::= { displayBatteriesMass 6 }



displayBatteriesMassStatus  OBJECT-TYPE
	SYNTAX     INTEGER {norm(0), battery is lost(1), battery cell asymmetry(2)}
	ACCESS     read-only
	STATUS     mandatory
	DESCRIPTION 
		"Battery status flags"
	::= { displayBatteriesMass 7 }

displayBatteriesCell1Voltage  OBJECT-TYPE
	SYNTAX     INTEGER (0..65535)
	ACCESS     read-only
	STATUS     mandatory
	DESCRIPTION 
		"Voltage of cell No. 1 in 0.1V"
	::= { displayBatteriesCell 1 }	

displayBatteriesCell2Voltage  OBJECT-TYPE
	SYNTAX     INTEGER (0..65535)
	ACCESS     read-only
	STATUS     mandatory
	DESCRIPTION 
		"Voltage of cell No. 2 in 0.1V"
	::= { displayBatteriesCell 2 }

displayBatteriesCell3Voltage  OBJECT-TYPE
	SYNTAX     INTEGER (0..65535)
	ACCESS     read-only
	STATUS     mandatory
	DESCRIPTION 
		"Voltage of cell No. 3 in 0.1V"
	::= { displayBatteriesCell 3 }

displayBatteriesCell4Voltage  OBJECT-TYPE
	SYNTAX     INTEGER (0..65535)
	ACCESS     read-only
	STATUS     mandatory
	DESCRIPTION 
		"Voltage of cell No. 4 in 0.1V"
	::= { displayBatteriesCell 4 }

displayBatteriesCell5Voltage  OBJECT-TYPE
	SYNTAX     INTEGER (0..65535)
	ACCESS     read-only
	STATUS     mandatory
	DESCRIPTION 
		"Voltage of cell No. 5 in 0.1V"
	::= { displayBatteriesCell 5 }	

displayBatteriesCell1Imbalance  OBJECT-TYPE
	SYNTAX     INTEGER (0..65535)
	ACCESS     read-only
	STATUS     mandatory
	DESCRIPTION 
		"Imbalance of cell No. 1 in percent"
	::= { displayBatteriesCell 11 }

displayBatteriesCell2Imbalance  OBJECT-TYPE
	SYNTAX     INTEGER (0..65535)
	ACCESS     read-only
	STATUS     mandatory
	DESCRIPTION 
		"Imbalance of cell No. 2 in percent"
	::= { displayBatteriesCell 12 }

displayBatteriesCell3Imbalance  OBJECT-TYPE
	SYNTAX     INTEGER (0..65535)
	ACCESS     read-only
	STATUS     mandatory
	DESCRIPTION 
		"Imbalance of cell No. 3 in percent"
	::= { displayBatteriesCell 13 }

displayBatteriesCell4Imbalance  OBJECT-TYPE
	SYNTAX     INTEGER (0..65535)
	ACCESS     read-only
	STATUS     mandatory
	DESCRIPTION 
		"Imbalance of cell No. 4 in percent"
	::= { displayBatteriesCell 14 }

displayBatteriesCell5Imbalance  OBJECT-TYPE
	SYNTAX     INTEGER (0..65535)
	ACCESS     read-only
	STATUS     mandatory
	DESCRIPTION 
		"Imbalance of cell No. 5 in percent"
	::= { displayBatteriesCell 15 }

displayBatteriesCell1ImbalanceStatus  OBJECT-TYPE
	SYNTAX     INTEGER (0..65535)
	ACCESS     read-only
	STATUS     mandatory
	DESCRIPTION 
		"Imbalance status cell No. 1 (0 - normal, 1 - deviation of the cell voltage from the average cell voltage above the set threshold )"
	::= { displayBatteriesCell 21 }	

displayBatteriesCell2ImbalanceStatus  OBJECT-TYPE
	SYNTAX     INTEGER (0..65535)
	ACCESS     read-only
	STATUS     mandatory
	DESCRIPTION 
		"Imbalance status cell No. 2 (0 - normal, 1 - deviation of the cell voltage from the average cell voltage above the set threshold )"
	::= { displayBatteriesCell 22 }	

displayBatteriesCell3ImbalanceStatus  OBJECT-TYPE
	SYNTAX     INTEGER (0..65535)
	ACCESS     read-only
	STATUS     mandatory
	DESCRIPTION 
		"Imbalance status cell No. 3 (0 - normal, 1 - deviation of the cell voltage from the average cell voltage above the set threshold )"
	::= { displayBatteriesCell 23 }	

displayBatteriesCell4ImbalanceStatus  OBJECT-TYPE
	SYNTAX     INTEGER (0..65535)
	ACCESS     read-only
	STATUS     mandatory
	DESCRIPTION 
		"Imbalance status cell No. 4 (0 - normal, 1 - deviation of the cell voltage from the average cell voltage above the set threshold )"
	::= { displayBatteriesCell 24 }	

displayBatteriesCell5ImbalanceStatus  OBJECT-TYPE
	SYNTAX     INTEGER (0..65535)
	ACCESS     read-only
	STATUS     mandatory
	DESCRIPTION 
		"Imbalance status cell No. 5 (0 - normal, 1 - deviation of the cell voltage from the average cell voltage above the set threshold )"
	::= { displayBatteriesCell 25 }	

displaySpecialsControlByte  OBJECT-TYPE
	SYNTAX     INTEGER {Special functions off(0), capacity control(1), equalization charge(10)}
	ACCESS     read-only
	STATUS     mandatory
	DESCRIPTION 
		"Special function status"
	::= { displaySpecials 1 }


displaySpecialsTrapMessage  OBJECT-TYPE
	SYNTAX     DisplayString (SIZE(0..30))
	ACCESS     read-only
	STATUS     mandatory
	DESCRIPTION 
		""
	::= { displaySpecials 4 }

displaySpecialsTrapValue  OBJECT-TYPE
	SYNTAX     INTEGER (0..65535)
	ACCESS     read-only
	STATUS     mandatory
	DESCRIPTION 
		""
	::= { displaySpecials 5 }



displayEventsTable  OBJECT-TYPE
	SYNTAX SEQUENCE OF DisplayEventsEntry
	ACCESS     not-accessible
	STATUS     mandatory
	DESCRIPTION 
		""
	::= { ibep1U 9 }

displayEventsEntry  OBJECT-TYPE
	SYNTAX 	DisplayEventsEntry
	ACCESS     not-accessible
	STATUS     mandatory
	DESCRIPTION 
		""
	INDEX { displayEventNumber }
	::= { displayEventsTable 1 }

DisplayEventsEntry ::= SEQUENCE {
	displayEventNumber
		DisplayString
}

displayEventNumber  OBJECT-TYPE
	SYNTAX     DisplayString
	ACCESS     read-only
	STATUS     mandatory
	DESCRIPTION 
		""
	::= { displayEventsEntry 1 }

displayDEBUGcommanLength  OBJECT-TYPE
	SYNTAX     INTEGER (0..65535)
	ACCESS     read-write
	STATUS     mandatory
	DESCRIPTION 
		""
	::= { displayDEBUG 1 }

displayDEBUGcommandSENT  OBJECT-TYPE
	SYNTAX     DisplayString (SIZE(0..255))
	ACCESS     read-only
	STATUS     mandatory
	DESCRIPTION 
		""
	::= { displayDEBUG 2 }

displayDEBUGreplyRCVD  OBJECT-TYPE
	SYNTAX     DisplayString (SIZE(0..255))
	ACCESS     read-only
	STATUS     mandatory
	DESCRIPTION 
		""
	::= { displayDEBUG 3 }

displayDEBUGsentPckts  OBJECT-TYPE
	SYNTAX     INTEGER (0..65535)
	ACCESS     read-only
	STATUS     mandatory
	DESCRIPTION 
		""
	::= { displayDEBUG 4 }

displayDEBUGrcvdPckts  OBJECT-TYPE
	SYNTAX     INTEGER (0..65535)
	ACCESS     read-only
	STATUS     mandatory
	DESCRIPTION 
		""
	::= { displayDEBUG 5 }

displayDEBUGSetVar  OBJECT-TYPE
	SYNTAX     INTEGER (0..65535)
	ACCESS     read-write
	STATUS     mandatory
	DESCRIPTION 
		""
	::= { displayDEBUG 6 }

displayFuseTable  OBJECT-TYPE
	SYNTAX SEQUENCE OF DisplayPSUEntry
	ACCESS     not-accessible
	STATUS     mandatory
	DESCRIPTION 
		"Table of fuses"
	::= { ibep1U 14 }

displayFuseEntry  OBJECT-TYPE
	SYNTAX 	DisplayFuseEntry
	ACCESS     not-accessible
	STATUS     mandatory
	DESCRIPTION 
		"Fuse listing"
	INDEX { displayFuseNumber }
	::= { displayFuseTable 1 }

DisplayFuseEntry ::= SEQUENCE {
	displayFuseNumber
		INTEGER,
	displayFuseState
		INTEGER
}

displayFuseNumber  OBJECT-TYPE
	SYNTAX     INTEGER
	ACCESS     read-only
	STATUS     mandatory
	DESCRIPTION 
		"Number of Fuse"
	::= { displayFuseEntry 1 }

displayFuseState  OBJECT-TYPE
	SYNTAX     INTEGER
	ACCESS     read-only
	STATUS     mandatory
	DESCRIPTION 
		"State of Fuse"
	::= { displayFuseEntry 2 }	

displayLogicalInputTable  OBJECT-TYPE
	SYNTAX SEQUENCE OF displayLogicalInputEntry
	ACCESS     not-accessible
	STATUS     mandatory
	DESCRIPTION 
		"Table of logical inputs"
	::= { ibep1U 15 }

displayLogicalInputEntry  OBJECT-TYPE
	SYNTAX 	DisplayLogicalInputEntry
	ACCESS     not-accessible
	STATUS     mandatory
	DESCRIPTION 
		"Logical inputs listing"
	INDEX { displayLogicalInputNumber }
	::= { displayLogicalInputTable 1 }

DisplayLogicalInputEntry ::= SEQUENCE {
	displayLogicalInputNumber
		INTEGER,
	displayLogicalInputState
		INTEGER
}

displayLogicalInputNumber  OBJECT-TYPE
	SYNTAX     INTEGER
	ACCESS     read-only
	STATUS     mandatory
	DESCRIPTION 
		"Number of logical input"
	::= { displayLogicalInputEntry 1 }

displayLogicalInputState  OBJECT-TYPE
	SYNTAX     INTEGER
	ACCESS     read-only
	STATUS     mandatory
	DESCRIPTION 
		"Alarm state of logical input"
	::= { displayLogicalInputEntry 2 }	

displayExtTemperature  OBJECT-TYPE
	SYNTAX     INTEGER (0..65535)
	ACCESS     read-write
	STATUS     mandatory
	DESCRIPTION 
		"Outside temperature sensor reading"
	::= { displayExtTemper 1 }

displayExtTemperatureSensorInvalid  OBJECT-TYPE
	SYNTAX     INTEGER (0..65535)
	ACCESS     read-write
	STATUS     mandatory
	DESCRIPTION 
		"Outside temperature sensor malfunction (1 - faulty)"
	::= { displayExtTemper 2 }


alarmTrap  TRAP-TYPE
	ENTERPRISE entSPA-SIB
	VARIABLES { displaySpecialsTrapMessage, 
		displaySpecialsTrapValue }
	DESCRIPTION 
		"Messages:
		Power unit started
		Main power is off
		Main power is on
		Battery alarm, not founded
		Battery alarm, asimetry
		Battery alarm cleared
		Alarm Fuse #1 broken
		Alarm Fuse #2 broken
		Alarm Fuse #3 broken
		Alarm, PSU #1 disabled
		Alarm, PSU #2 disabled
		PSU #1 alarm cleared
		PSU #2 alarm cleared
		SK #1 is on
		SK #2 is on
		SK #3 is on
		SK #4 is on
		SK #1 is off
		SK #2 is off
		SK #3 is off
		SK #4 is off
		Alarm, temperature of sensor #1 is above the threshold
		Alarm, temperature of sensor #2 is above the threshold
		Alarm, temperature of sensor #3 is above the threshold
		Alarm, temperature of sensor #4 is above the threshold
		Alarm, temperature of sensor #1 is below the threshold
		Alarm, temperature of sensor #2 is below the threshold
		Alarm, temperature of sensor #3 is below the threshold
		Alarm, temperature of sensor #4 is below the threshold
		Temperature of sensor #1 is normal
		Temperature of sensor #2 is normal
		Temperature of sensor #3 is normal
		Temperature of sensor #4 is normal
		External temperature sensor defective
		External temperature sensor is OK"
	::= 3
END
